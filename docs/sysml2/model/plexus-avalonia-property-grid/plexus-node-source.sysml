package PlexusAvaloniaPropertyGrid {
    private import SoftwareItemMetadata::*;

    part def PlexusNodeSource {
        doc /* The Plexus adapter sources that show and edit a node (name, declared properties, host data on a working copy), an annotation or a group in the property grid, with every commit as one undo entry of the diagram. */

        metadata info : SoftwareInfo {
            sourceFiles = ("src/DemaConsulting.Plexus.Avalonia.PropertyGrid/Diagrams/NodePropertySource.cs", "src/DemaConsulting.Plexus.Avalonia.PropertyGrid/Diagrams/AnnotationPropertySource.cs", "src/DemaConsulting.Plexus.Avalonia.PropertyGrid/Diagrams/GroupPropertySource.cs", "src/DemaConsulting.Plexus.Avalonia.PropertyGrid/Diagrams/ElementEditing.cs", "src/DemaConsulting.Plexus.Avalonia.PropertyGrid/Diagrams/ElementPropertyItem.cs", "src/DemaConsulting.Plexus.Avalonia.PropertyGrid/Diagrams/WorkingValues.cs", "src/DemaConsulting.Plexus.Avalonia.PropertyGrid/Diagrams/DefinitionConverter.cs", "src/DemaConsulting.Plexus.Avalonia.PropertyGrid/Diagrams/PlexusSourceRegistration.cs", "src/DemaConsulting.Plexus.Avalonia.PropertyGrid/Diagrams/NamespaceDoc.cs");
            testFiles = ("test/DemaConsulting.Plexus.Avalonia.PropertyGrid.Tests/NodePropertySourceTests.cs", "test/DemaConsulting.Plexus.Avalonia.PropertyGrid.Tests/NodeFixture.cs");
            designFiles = ("docs/design/plexus-avalonia-property-grid/plexus-node-source.md");
            verificationFiles = ("docs/verification/plexus-avalonia-property-grid/plexus-node-source.md");
            requirementFiles = ("docs/reqstream/plexus-avalonia-property-grid/plexus-node-source.yaml");
        }
    }
}
