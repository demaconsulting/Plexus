package Plexus {
    part def Demo {
        doc /* Demonstration greeting class showing how a DEMA Consulting .NET library class should be structured, documented, and tested. */

        comment sourceRef /* Source: src/DemaConsulting.Plexus/Demo.cs */
        comment testRef /* Test: test/DemaConsulting.Plexus.Tests/DemoTests.cs */
        comment designRef /* Design: docs/design/plexus/demo.md */
        comment verificationRef /* Verification: docs/verification/plexus/demo.md */
        comment reqRef /* Requirements: docs/reqstream/plexus/demo.yaml */
    }
}
